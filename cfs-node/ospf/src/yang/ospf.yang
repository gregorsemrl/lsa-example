module ospf {
  namespace "http://com/example/ospf";
  prefix ospf;

  import ietf-inet-types { prefix inet; }
  import tailf-ncs { prefix ncs; }
  import tailf-common { prefix tailf; }
  import lsa-dispatch-map { prefix map; }
  
  list ospf {
    tailf:info "Services for OSPF configuration (NSO300 LSA training)";
    key name;

    uses ncs:service-data;
    ncs:servicepoint "ospf";

    leaf name {
      type string;
    }


    leaf rfs-node {
      type leafref {
        path "/map:lsa-dispatch-map/map:rfs-node";
      }
    }

    leaf managed-device {
      type leafref {
        path "deref(../rfs-node)/../map:managed-device/map:name";
      }
    }


        
       

        list ospfProcess {
          tailf:info "OSPF Configuration list";
          key "id";

          leaf id {
            tailf:info "OSPF Process ID";
            type uint32;
          }

          leaf ip-address {
                      tailf:info "OSPF IP address";
                      type inet:ipv4-address;
          }

          leaf netmask {
                      tailf:info "OSPF Netmask";
                      type inet:ipv4-address;
          }

          leaf area {
            tailf:info "OSPF Area ID";
            type uint32;
          }
        }
      }

   
  }
